submodule Cisco-IOS-XE-interfaces {
    belongs-to Cisco-IOS-XE-native {
      prefix ios;
    }
  
    import ietf-inet-types {
      prefix inet;
    }
  
  
    import Cisco-IOS-XE-types {
      prefix ios-types;
    }
  
    import Cisco-IOS-XE-features {
      prefix ios-features;
    }
  
    import Cisco-IOS-XE-interface-common {
      prefix ios-ifc;
    }
  
    organization
      "Cisco Systems, Inc.";
  
    contact
      "Cisco Systems, Inc.
       Customer Service
  
       Postal: 170 W Tasman Drive
       San Jose, CA 95134
  
       Tel: +1 1800 553-NETS
  
       E-mail: cs-yang@cisco.com";
  
    description
      "Cisco XE Native Interfaces Yang model.
       Copyright (c) 2016-2017 by Cisco Systems, Inc.
       All rights reserved.";
  
    // =========================================================================
    // REVISION
    // =========================================================================
    revision 2017-08-30 {
      description
        "Move UTD interface support";
    }
  
    revision 2017-08-21 {
      description
        "Add HundredGigE interface support";
    }
  
    revision 2017-08-16 {
      description
        "This revision has changes for new 5gig and 25gig interfaces addition";
    }
  
    revision 2017-08-02 {
      description
        "Added Stackwise Virtual Interface commands";
    }
  
    revision 2017-07-31 {
      description
        "Add dependency between ip primary and secondary";
    }
  
    revision 2017-07-20 {
      description
        "Change mtu range";
    }
    revision 2017-07-07 {
      description
        "Add ipv6 source-guard support and storm-control broadcast/multicast falling-threshold for int gig";
    }
  
    revision 2017-06-28 {
       description
         "Add nve support for special interface ucse, Ethernet-Internal and Service-Engine";
     }
  
    revision 2017-06-27 { 
      description
        "Extend FastEthernet and FortyGigabitEthernet to allow subinterfaces";
    }
  
    revision 2017-06-14 { 
       description
         "Add nve support for ingress-replication"; 
     }
  
    revision 2017-06-01 { 
       description
         "Add dependency for interface ip address to encapsulation/dot1Q";
     }
  
    revision 2017-05-11 { 
      description
        "fix hold-queue to allow support for both in and out queues.";
    }
    revision 2017-04-20 { 
      description
        "Added ipv6/tcp/adjust-mss support, fixed loopback dampening issue, fixed ipv6 address autoconfig issue";
    }
    revision 2017-04-17 {
      description 
        "Addition of support for group-based policy command";
    }
    revision 2017-03-24 {
      description
        "Removed bandwidth range constraints";
    }
    revision 2017-03-04 {
      description
        "Changed LISP key type to string to support OC mapping, removed Fast/Forty Ethernet pattern";
    }
  
    revision 2017-02-07 {
      description
        "Initial revision";
    }
  
    grouping nve-member-vni-mcast-group-grouping {
       container mcast-group {
         leaf multicast-group-min {
           description
             "Starting Multicast Group IPv4 Address";
           type inet:ipv4-address;
         }
         leaf multicast-group-max {
           description
             "Ending Multicast Group IPv4 Address";
           type inet:ipv4-address;
         }
       }
     }
   
     grouping nve-member-vni-grouping {
       leaf ingress-replication {
         description
           "Ingress Replication or Unicast mode for vni(s)";
         type inet:ipv4-address;
       }
       uses nve-member-vni-mcast-group-grouping;
     }
  
  
    grouping storm-control-threshold-grouping {
      container level {
        description
          "Set storm suppression level on this interface";
        container threshold {
          description
            "Broadcast address storm control";
          leaf rising-threshold {
            description
              "Enter rising threshold";
            type decimal64 {
              fraction-digits 2;
              range "0..100";
            }
          }
          leaf falling-threshold  {
            description
              "Enter falling threshold";
            type decimal64 {
              fraction-digits 2;
              range "0..100";
            }
          }
        }
        container bps {
          description
            "Enter suppression level in bits per second";
          leaf rising-threshold {
            description
              "Enter rising threshold - <0.0 - 10000000000.0>[k|m|g]>";
            type ios-types:storm-control-threshold-type;
          }
          leaf falling-threshold  {
            description
              "Enter falling threshold - <0.0 - 10000000000.0>[k|m|g]> ";
            type ios-types:storm-control-threshold-type;
          }
        }
        container pps {
          description
            "Enter suppression level in packets per second";
          leaf rising-threshold {
            description
              "Enter rising threshold - <0.0 - 10000000000.0>[k|m|g]";
            type ios-types:storm-control-threshold-type;
          }
          leaf falling-threshold  {
            description
              "Enter falling threshold - <0.0 - 10000000000.0>[k|m|g] ";
            type ios-types:storm-control-threshold-type;
          }
        }
      }
    }
    grouping ethernet-grouping {
      choice ethernet-choice {
        leaf FastEthernet {
          description
            "FastEthernet IEEE 802.3";
          type string;
        }
        leaf GigabitEthernet {
          description
            "GigabitEthernet IEEE 802.3z";
          type string;
        }
        leaf FiveGigabitEthernet {
          description
            "Five Gigabit Ethernet ";
          type string;
        }
        leaf Port-channel {
          description
            "Ethernet Channel of interfaces";
          type uint32;
        }
        leaf TenGigabitEthernet {
          description
            "Ten Gigabit Ethernet";
          type string;
        }
        leaf TwentyFiveGigabitEthernet {
          description
            "Twenty Five Gigabit Ethernet ";
          type string;
        }
        leaf FortyGigabitEthernet {
          description
            "Forty Gigabit Ethernet";
          type string;
        }
        leaf HundredGigE {
          description
            "Hundred Gigabit Ethernet";
          type string;
        }
        leaf vlan {
          description
            "Catalyst Vlans";
          type uint16 {
            range "1..4094";
          }
        }
      }
    }
  
   grouping interface-negotiation-grouping {
       container negotiation {
         description
           "Select autonegotiation mode";
         leaf auto {
           description
             "Enable link autonegotiation";
           type boolean;
         }
       }
     }
    
     grouping interface-switchport-grouping {
       container switchport-wrapper {
         container switchport {
   
           // interface * / switchport access
           container access {
             description
               "Set access mode characteristics of the interface";
             leaf vlan {
               description
                 "Set VLAN when interface is in access mode";
               type uint16 {
                  range "1..4094";
               }
             }
           }
   
           // interface * / switchport mode
           leaf mode {
             description
               "Set trunking mode of the interface";
             type enumeration {
               enum "access";
               enum "trunk";
             }
           }
   
           // interface * / switchport trunk
           container trunk {
             description
               "Set trunking characteristics of the interface";
             // interface * / switchport trunk allowed
             container allowed {
               description
                 "Set allowed VLAN characteristics when interface is in trunking mode";
               // interface * / switchport trunk allowed vlan
               container vlan {
                 description
                   "Set allowed VLANs when interface is in trunking mode";
                 choice vlan-choice {
                   leaf vlans {
                     type string;
                   }
                   leaf add {
                     description
                       "VLAN IDs of the allowed VLANs when this port is in trunking mode";
                     type union {
                       type uint16;
                       type string;
                     }
                   }
                   leaf all {
                     description
                       "all VLANs";
                     type empty;
                   }
                   leaf-list except {
                     description
                       "all VLANs except the following";
                     type union {
                       type uint16;
                       type string;
                     }
                   }
                   leaf none {
                     description
                       "no VLANs";
                     type empty;
                   }
                   leaf remove {
                     description
                       "VLAN IDs of disallowed VLANS when this port is in trunking mode";
                     type union {
                       type uint16;
                       type string;
                     }
                   }
                 }
               }
             }
             container native {
               leaf vlan {
                 description
                   "Set VLAN when interface is in access mode";
                 type uint16 {
                   range "1..4094";
                 }
               }
             }
           }
         }
       }
     }
  
    grouping interface-common-grouping {
      // interface * / description
      leaf description {
        description
          "Interface specific description";
        type string {
          length "0..240";
        }
      }
  
      // interface * / no switchport
      container switchport-conf {
         leaf switchport {
           type boolean;
         }
         if-feature ios-features:switching-platform;
      }
  
      container switchport {
         description
           "Set switching mode characteristics";
         if-feature ios-features:switching-platform;
      }
     
      // interface * / stackwise-virtual
      container stackwise-virtual {
         description
           "Configure stackwise-virtual link values";
          leaf link {
            type uint8 {
              range 1..2;
            }
          }
          leaf dual-active-detection {
            type empty;
          }
      }
  
      // interface * / mac-address
      leaf mac-address {
        description
          "Manually set interface MAC address";
      type string;
      }
  
      // interface * / shutdown
      leaf shutdown {
        description
          "Shutdown the selected interface";
        type empty;
      }
  
      // interface arp *
      container arp {
        description "Set arp type (arpa, probe, snap), timeout, log options or 
                     packet priority";
        leaf timeout {
          description
            "Set ARP cache timeout";
          type uint32{
            range "0..2147483";
          }
        }
      }
  
      // interface backup * /
      container backup {
        description
          "Modify backup parameters";
        container delay {
          description
            "Delays before backup line up or down transitions";
          leaf failure {
  
            description
              "Seconds";
            type union {
              type uint32 {
                range "0..4294967294";
              }
              type enumeration {
                enum "never";
              }
            }
          }
          leaf secondary-disable {
            description
              "Seconds";
            type union {
              type uint32 {
                range "0..4294967294";
              }
              type enumeration {
                enum "never";
              }
            }
          }
        }
  
        container interface {
          description
            "Configure an interface as a backup";
            uses ios-ifc:interface-grouping;
        }
  
        container load {
          description
            "Load thresholds for line up or down transitions";
          leaf kickin {
            description
              "Percentage";
            type union {
              type uint32 {
                range "0..100";
              }
              type enumeration {
                enum "never";
              }
            }
          }
          leaf kickout {
            description
              "Percentage";
            type union {
              type uint32 {
                range "0..100";
              }
              type enumeration {
                enum "never";
              }
            }
          }
        }
      }
  
      // interface cemoudp * /
      container cemoudp {
        description
          "cemoudp";
        container reserve {
          leaf acr {
            type uint8;
          }
        }
      }
  
      //interface * / cws-tunnel
      container cws-tunnel {
        description
          "Configure Cloud Web Security Tunnel";
        leaf in {
          description
            "Inbound traffic";
          type empty;
        }
        container out {
          description
            "Outbound traffic";
          leaf tunnel-number {
            description
              "Outboud traffic tunnel identifier";
            type uint16 {
              range "0..65534";
            }
          }
        }
      }
  
      // interface * / l2protocol-tunnel
      container l2protocol-tunnel {
        description
          "Tunnel Layer2 protocols";
        presence "true";
        leaf cdp {
          description
            "Cisco Discovery Protocol";
          type empty;
        }
        container drop-threshold {
          description
            "Set drop threshold for protocol packets";
          leaf packet-rate {
            type uint16 {
              range "1..4096";
            }
          }
          leaf cdp {
            description
              "Cisco Discovery Protocol";
            type uint16 {
              range "1..4096";
            }
          }
          leaf stp {
            description
              "Spanning Tree Protocol";
            type uint16 {
              range "1..4096";
            }
          }
          leaf vtp {
            description
              "Vlan Trunking Protocol";
            type uint16 {
              range "1..4096";
            }
          }
        }
        container shutdown-threshold {
          description
            "Set shutdown threshold for protocol packets";
          leaf packet-rate {
            type uint16 {
              range "1..4096";
            }
          }
          leaf cdp {
            description
              "Cisco Discovery Protocol";
            type uint16 {
              range "1..4096";
            }
          }
          leaf stp {
            description
              "Spanning Tree Protocol";
            type uint16 {
              range "1..4096";
            }
          }
          leaf vtp {
            description
              "Vlan Trunking Protocol";
            type uint16 {
              range "1..4096";
            }
          }
        }
        leaf stp {
          description
            "Spanning Tree Protocol";
          type empty;
        }
        leaf vtp {
          description
            "Vlan Trunking Protocol";
          type empty;
        }
      }
  
      // interface * / encapsulation
      container encapsulation {
        description
          "Set encapsulation type for an interface";
        container dot1Q {
          description
            "IEEE 802.1Q Virtual LAN";
          leaf vlan-id {
            type uint16 {
              range "1..4094";
            }
          }
          leaf native {
            description
              "Make this as native vlan";
            type empty;
          }
        }
        // interface * / encapsulation isl
        container isl {
          description
            "Inter Switch Link - Virtual LAN encapsulation";
          leaf vlan-id {
            type uint16 {
              range "1..4095";
            }
          }
        }
        // interface * / encapsulation ppp
        container ppp {
          description
            "Point-to-Point protocol";
          presence "true";
        }
        // interface * / encapsulation slip
        container slip {
          description
            "Serial Line IP";
          presence "true";
        }
        // interface * / encapsulation frame-relay
        container frame-relay {
          description
            "Frame Relay networks";
          presence "true";
          leaf ietf {
            description
              "Use RFC1490/RFC2427 encapsulation";
            type empty;
          }
        }
      }
  
      // interface * / no fair-queue
      container fair-queue-conf {
        leaf fair-queue {
          type boolean;
        }
      }
  
      // interface * / fair-queue
      container fair-queue {
        description
          "Enable Fair Queuing on an Interface";
        leaf incomplete {
          type empty;
        }
      }
  
      // interface * / flowcontrol
      container flowcontrol {
        description
          "Configure flow operation.";
        leaf receive {
          description
            "Configure receiving flow operation";
          type enumeration {
            enum "desired";
            enum "off";
            enum "on";
          }
        }
        leaf send {
          description
            "Configure sending flow operation";
          type enumeration {
            enum "desired";
            enum "off";
            enum "on";
          }
        }
      }
  
      // interface * / isis
      container isis {
        description
          "IS-IS commands";
        // @mount Cisco-IOS-XE-isis
      }
  
      // interface * / full-duplex
      // results in "duplex full"
  
      // interface * / keepalive
      choice keepalive-choice {
        leaf keepalive {
          description
            "Enable keepalive";
          type boolean;
        }
        container keepalive-settings {
          container keepalive {
            description
              "Enable keepalive";
            presence "true";
            leaf period {
              type uint16 {
                range "0..32767";
              }
            }
            leaf retries {
              type uint8;
            }
          }
        }
      }
  
      // interface * / bfd
      container bfd {
        description
          "BFD interface configuration commands";
        // @mount Cisco-IOS-XE-bfd
      }
  
      // interface * / bandwidth
      container bandwidth {
        description
          "Set bandwidth informational parameter";
        container receive {
          description
            "Specify receive-side bandwidth";
          leaf inherit {
            description
              "Specify how bandwidth is inherited";
            type empty;
          }
          leaf kilobits {
            type uint32;
          }
        }
        container inherit {
          description
            "Specify how bandwidth is inherited";
          presence "true";
          leaf kilobits {
            type uint32;
          }
        }
        leaf qos-reference {
          description
            "Reference bandwidth for QOS";
          type uint32;
        }
        leaf kilobits {
          type uint32;
        }
      }
  
      // interface * / dampening
      container dampening {
        description
          "Enable event dampening";
        leaf dampening-time {
          description
            "<1-30>;;Half-life time for penalty";
          type uint16 {
            range "1..30";
          }
        }
        leaf start-reusing-time {
          description
            "<1-20000>;;Value to start reusing an interface";
          type uint16 {
            range "1..20000";
          }
        }
        leaf start-supressing-time {
          description
            "<1-20000>;;Value to start supressing an interface";
          type uint16 {
            range "1..20000";
          }
        }
        leaf maximum-supressing-time {
          description
            "<1-255>;;Maximum duration to suppress an interface";
          type uint16 {
            range "1..255";
          }
        }
        container restart {
          description
            "Enable restart penalty";
          leaf restart {
            description
              "Enable restart penalty";
            type empty;
          }
          leaf restart-penalty {
            description
              "<1-20000>;;Penalty applied at restart";
            type uint16 {
              range "1..20000";
            }
          }
        }
      }
  
      // interface * / if-state
      leaf if-state {
        type enumeration {
          enum "nhrp";
        }
      }
  
      // interface * / delay
      leaf delay {
        description
          "Specify interface throughput delay";
        type uint32 {
          range "1..16777215";
        }
      }
  
      // interface * / domain
      container domain {
        description
          "Specify a domain";
        leaf name {
          type string;
        }
        leaf path {
          description
            "Specify a service provider for this interface";
          type string;
        }
        leaf internet-bound {
          description
            "Specify Internet-bound interface";
          type empty;
        }
        leaf path-id {
          description
            "Specify service provider path-id for this interface";
          type uint8;
        }
        leaf path-last-resort {
          description
            "Specify if you want this interface to be a path of last resort";
          type empty;
        }
        leaf zero-sla {
          description
            "Specify if you want this interface to be a 0-sla interface";
          type empty;
        }
      }
  
      // interface * / hold-queue
      list hold-queue {
        description
          "Set hold queue depth";
        key "direction";
        leaf direction {
          type enumeration {
            enum "in";
            enum "out";
          }
        }
        leaf queue-length {
          type uint16 {
            range "0..4096";
          }
        }
      }
  
      // interface * / mpls
      container mpls {
        // @mount Cisco-IOS-XE-mpls
      }
  
      // interface * / vrf forwarding
  
      // interface * / ip vrf forwarding
      choice vrf-choice {
        container ip-vrf {
          container ip {
            container vrf {
              leaf forwarding {
                description
                  "Configure forwarding table";
                type string;
              }
            }
          }
        }
        container vrf {
          description
            "VPN Routing/Forwarding parameters on the interface";
            // interface * / vrf forwarding
          leaf forwarding {
            description
              "Configure forwarding table";
            type string;
          }
        }
      }
  
      // interface * / ip
      container ip {
        description
          "Interface Internet Protocol config commands";
        // interface * / ip admission
        leaf admission {
          description
          "Apply Network Admission Control";
          type string;
        }
          // interface * / ip access-group
        container access-group {
          description
            "Specify access control for packets";
          container in {
            choice apply-type {
              case apply-common {
                container common-acl {
                  leaf common {
                    description
                      "specify ipv4 common ACL for packet filtering";
                    type ios-types:exp-acl-type;
                    mandatory true;
                  }
                  leaf in {
                    description
                      "inbound packets";
                    type empty;
                  }
                }
              }
              case apply-intf {
                container acl {
                  leaf acl-name {
                    type ios-types:exp-acl-type;
                    mandatory true;
                  }
                  leaf in {
                    description
                      "inbound packets";
                    type empty;
                  }
                }
              }
            }
          }
          container out {
            choice apply-type {
              case apply-common {
                container common-acl {
                  leaf common {
                    description
                      "specify ipv4 common ACL for packet filtering";
                    type ios-types:exp-acl-type;
                    mandatory true;
                  }
                  leaf out {
                    description
                      "outbound packets";
                    type empty;
                  }
                }
              }
              case apply-intf {
                container acl {
                  leaf acl-name {
                    type ios-types:exp-acl-type;
                    mandatory true;
                  }
                  leaf out {
                    description
                      "outbound packets";
                    type empty;
                  }
                }
              }
            }
          }
        }
  
        // interface * / ip arp
        container arp {
          description
            "Configure ARP features";
          container inspection {
            description
              "Arp Inspection configuration";
            container limit {
              description
                "Configure Rate limit of incoming ARP packets";
              leaf none {
                description
                  "No limit";
                type empty;
              }
              leaf rate {
                description
                  "Rate Limit";
                type uint32;
              }
            }
            leaf trust {
              description
                "Configure Trust state";
              type empty;
            }
          }
        }
  
        // interface * / ip vrf
        container vrf {
          description
            "VPN Routing/Forwarding parameters on the interface";
          leaf receive {
            description
              "Add Interface Address into VRF Table";
            type string;
          }
          leaf sitemap {
            description
              "Configure route-map for routesreceived from this site";
            type string;
            // Note: no dependency to /ios:route-map
          }
  
          container forwarding {
            description "Configure forwarding table";
            leaf Liin-vrf {
              type empty;
            }
  
            leaf mgmtVrf {
              type empty;
            }
  
            leaf word {
              type string;
            }
          }
        }
  
        // interface * / ip address
        choice address-choice {
          // interface * / ip unnumbered
          leaf unnumbered {
            description
              "Enable IP processing without an explicit address";
            type string;
          }
          // interface * / no ip address
          container no-address {
            leaf address {
              type boolean;
            }
          }
          // interface * / ip address XXX
          container address {
            description
              "Set the IP address of an interface";
            choice address-choice {
              case fixed-case {
                container primary {
                  leaf address {
                    type inet:ipv4-address;
                  }
                  leaf mask {
                    type inet:ipv4-address;
                  }
                }
                list secondary {
                  key "address";
                  leaf address {
                    type inet:ipv4-address;
                  }
                  leaf mask {
                    mandatory true;
                    type inet:ipv4-address;
                  }
                  leaf secondary {
                    description
                      "Make this IP address a secondary address";
                    mandatory true;
                    type empty;
                  }
                }
              }
              case dhcp-case {
                container dhcp {
                  description
                    "IP Address negotiated via DHCP";
                  presence "IP Address negotiated via DHCP";
                  container client-id {
                    description
                      "Specify client-id to use";
                    uses ethernet-grouping;
                  }
                  leaf hostname {
                    description
                      "Specify value for hostname option";
                    type string;
                  }
                }
              }
              case negotiated-case {
                leaf negotiated {
                  description
                    "IP Address negotiated via IKEv2 Modeconfig";
                  type empty;
                }
              }
            }
          }
        }
  
        // interface * / ip directed-broadcast
        leaf directed-broadcast {
          description
            "Enable forwarding of directed broadcasts";
          type ios-types:exp-acl-type;
        }
  
  
        // interface * / ip flow
        // @mount Cisco-IOS-XE-flow
  
        // interface * / ip hello-interval
        container hello-interval {
          description
            "Configures EIGRP-IPv4 hello interval";
          leaf eigrp {
            description
              "Enhanced Interior Gateway Routing Protocol (EIGRP)";
            type uint16;
          }
          leaf seconds {
            description
              "Seconds between hello transmissions";
            type uint16;
          }
        }
  
        // interface * / ip authentication
        container authentication {
          description
            "authentication subcommands";
          container key-chain {
            description
              "key-chain";
            leaf eigrp {
              description
                "Enhanced Interior Gateway Routing Protocol (EIGRP)";
              type uint16;
            }
            leaf name {
              description
                "name of key-chain";
              type string;
            }
          }
          container mode {
            description
              "mode";
            leaf eigrp {
              description
                "Enhanced Interior Gateway Routing Protocol (EIGRP)";
              type uint16;
            }
            leaf md5 {
              description
                "Keyed message digest";
              type empty;
            }
          }
        }
  
        // interface * / ip hold-time
        container hold-time {
          description
            "Configures EIGRP-IPv4 hold time";
          leaf eigrp {
            description
              "Enhanced Interior Gateway Routing Protocol (EIGRP)";
            type uint16;
          }
          leaf seconds {
            description
              "Seconds before neighbor is considered down";
            type uint16;
          }
        }
  
        // interface * / ip helper-address
        list helper-address {
          description
            "Specify a destination address for UDP broadcasts";
          key "address";
          leaf address {
            type inet:ipv4-address;
          }
          choice helper-choice {
            leaf global {
              description
                "Helper-address is global";
              type empty;
            }
            leaf vrf {
              description
                "VRF name for helper-address (if different from interface VRF)";
              type string;
            }
          }
        }
  
        // interface * / ip pim
        container pim {
          description
            "PIM interface commands";
          // @mount Cisco-IOS-XE-mcast
        }
  
        // interface * / ip policy
        container policy {
          description
            "Enable policy routing";
          leaf route-map {
            description
              "Policy route-map";
            type string;
          }
        }
  
        // interface * / ip local-proxy-arp
        leaf local-proxy-arp {
          description
            "Enable local-proxy ARP";
          type empty;
        }
  
        // interface * / ip proxy-arp
        leaf proxy-arp {
          description
            "Enable proxy ARP";
          type boolean;
        }
  
        // interface * / ip rip
        container rip {
          description "Router Information Protocol";
          container authentication {
            description "Authentication control";
            leaf key-chain {
              description "Authentication key-chain";
              type string;
            }
            container mode {
              description "Authentication mode";
              leaf md5 {
                description "Keyed message digest";
                type empty;
              }
              leaf text {
                description "Clear text authentication";
                type empty;
              }
            }
          }
        }
  
        // interface * / no ip route-cache
        container route-cache-conf {
          leaf route-cache {
            type boolean;
          }
        }
  
        // interface * / ip route-cache
        container route-cache {
          description
            "Enable fast-switching cache for outgoing packets";
          presence true;
          // interface * / ip route-cache cef
          leaf cef {
            description
              "Enable Cisco Express Forwarding";
            type boolean;
          }
  
          // interface * / ip route-cache flow
          leaf flow {
            description
              "Enable Flow fast-switching cache";
            type boolean;
          }
  
          // interface * / ip route-cache policy
          leaf policy {
            description
              "Enable fast-switching policy cache for outgoing packets";
            type boolean;
          }
  
          // interface * / ip route-cache same-interface
          leaf same-interface {
            description
              "Enable fast-switching on the same interface";
            type boolean;
          }
        }
        // interface * / ip router
        container router {
          description
            "IP router interface commands";
          container isis {
            description
              "IS-IS Routing for IP";
            presence "true";
            leaf tag {
              type string;
            }
          }
        }
  
        // interface * / ip igmp
  
        // interface * / ip redirects
        leaf redirects {
          description
            "Enable sending ICMP Redirect messages";
          type boolean;
        }
  
        // interface * / ip unreachables
        // @mount Cisco-IOS-XE-icmp
  
        // interface * / ip tcp
        container tcp {
          description
            "TCP header compression and other parameters";
          leaf adjust-mss {
            description
              "Adjust the mss of transit packets";
            type uint16 {
              range "500..1460";
            }
          }
        }
  
        // interface * / ip virtual-reassembly
        container virtual-reassembly {
          leaf max-reassemblies {
            type uint32;
          }
          leaf max-fragments {
            type uint32;
          }
          leaf timeout {
            type uint32;
          }
          leaf drop-fragments {
            type empty;
          }
          leaf in {
            type empty;
          }
        }
  
        // interface * / ip dhcp
        container dhcp {
          description
            "Configure DHCP parameters for this interface";
          // @mount Cisco-IOS-XE-dhcp
        }
  
        // interface * / ip mtu
        leaf mtu {
          description
            "Set IP Maximum Transmission Unit";
          type uint16 {
            range "68..9216";
          }
        }
  
         // interface * / no ip mroute-cache
        leaf mroute-cache {
          description
            "Enable switching cache for incoming multicast packets";
          type boolean;
        }
  
        // interface * / ip rsvp
        // @mount Cisco-IOS-XE-rsvp
  
        // interface * / ip summary-address
        container summary-address {
          list eigrp {
            key id;
            leaf id {
              type string;
            }
            leaf ip {
              type inet:ipv4-address;
            }
            leaf mask {
              type inet:ipv4-address;
            }
            leaf metric {
              type uint32;
            }
          }
        }
  
        // interface * / ip verify
        container verify {
          description
            "Enable per packet validation";
          container source {
            description
              "Validation of source address";
            presence true;
            container vlan {
              description
                "vlan specification";
              container dhcp-snooping {
                description
                  "snooping enable vlan";
                presence true;
                leaf port-security {
                  description
                    "port security";
                  type empty;
                }
              }
            }
          }
          container unicast {
            description
              "Enable per packet validation for unicast";
            container reverse-path {
              description
                "Reverse path validation of source address (old command format)";
              presence "true";
            }
            container source {
              description
                "Validation of source address";
              leaf reachable-via {
                description
                  "Specify reachability check to apply to the source address";
                type enumeration {
                  enum "any";
                  enum "rx";
                }
              }
              leaf allow-self-ping {
                description
                  "Allow router to ping itself (opens vulnerability in verification)";
                type empty;
              }
              leaf allow-default {
                description
                  "Allow default route to match when checking source address";
                type empty;
              }
            }
          }
        }
  
        // interface * / ip wccp
        // @mount Cisco-IOS-XE-wccp
      }
  
      // interface * / ipv6
      container ipv6 {
        description
          "IPv6 interface subcommands";
        container destination-guard {
          description "Configure ipv6 destination guard on the interface";
          presence true;
          leaf attach-policy {
            description "Apply a policy for feature ipv6 destguard";
            type string;
          }
        }
        container source-guard {
          description "Configure ipv6 source guard on the interface";
          presence true;
          leaf attach-policy {
            description "Apply a policy for feature ipv6 sourceguard";
            type string;
          }
        }
   
  
        // interface * / ipv6 dhcp
        container dhcp {
          description
            "IPv6 DHCP interface subcommands";
          // @mount Cisco-IOS-XE-dhcp
        }
  
        // interface * / ipv6 address
        container address {
          description
            "Configure IPv6 address on interface";
          container dhcp {
            description
              "Obtain IPv6 address from DHCP server";
            presence "true";
            leaf rapid-commit {
              description
                "rapid-commit for prefix delegation";
              type empty;
            }
          }
          container autoconfig {
            description
              "Obtain address using autoconfiguration";
            presence "true";
            leaf default {
              description
                "Insert default route";
              type empty;
            }
          }
          list prefix-list {
            key "prefix";
            leaf prefix {
              type ios-types:ipv6-prefix;
            }
            leaf anycast {
              description
                "Configure as an anycast";
              type empty;
            }
            leaf eui-64 {
              description
                "Use eui-64 interface identifier";
              type empty;
            }
          }
          list link-local-address {
            key "address";
            leaf address {
              type inet:ipv6-address;
            }
            leaf link-local {
              description
                "Use link-local address";
              type empty;
            }
          }
        }
  
        // interface * / ipv6 unnumbered
        leaf unnumbered {
          description
        "Preferred interface for source address selection";
          type string;
        }
  
        // interface * / ipv6 unreachables
        // @mount Cisco-IOS-XE-icmp
  
        // interface * / ipv6 enable
        leaf enable {
          description
            "Enable IPv6 on interface";
          type empty;
        }
        // interface * / ipv6 flow
        // @mount Cisco-IOS-XE-flow
  
        // interface * / ipv6 ospf
        // @mount Cisco-IOS-XE-ospf
  
        // interface * / ipv6 mtu
        leaf mtu {
          description
            "Set IPv6 Maximum Transmission Unit";
          type uint16 {
            range "1280..9216";
          }
        }
  
        //interface * / ipv6 nd
        container nd {
          description
            "IPv6 interface Neighbor Discovery subcommands";
          // @mount Cisco-IOS-XE-nd
        }
  
        // interface * / ipv6 redirects
        leaf redirects {
          description
            "Enable sending ICMP Redirect messages";
          type boolean;
        }
  
        // interface * / ipv6 tcp
        container tcp {
          description
            "TCP header compression and other parameters";
          leaf adjust-mss {
            description
              "Adjust the mss of transit packets";
            type uint16 {
              range "40..1454";
            }
          }
        }
  
        // interface * / ipv6 rip
        // @mount Cisco-IOS-XE-rip
  
        // interface * / ipv6 pim
        // @mount Cisco-IOS-XE-mcast
  
        // interface * / ipv6 traffic-filter
        list traffic-filter {
          description
            "Access control list for packets";
          key "direction";
          leaf direction {
            type enumeration {
              enum "in";
              enum "out";
            }
          }
          leaf access-list {
            type string;
          }
        }
  
        // interface * / ipv6 crypto
        // @mount Cisco-IOS-XE-crypto
  
      }
      // interface * / lisp
      //@mount Cisco-IOS-XE-lisp
  
  
      // interface * / load-interval
      leaf load-interval {
        description
          "Specify interval for load calculation for an interface";
        type uint16 {
          range "0..600";
        }
      }
  
      // interface * / logging
      container logging {
        description
          "Configure logging for interface";
        container event {
          description
            "Interface events";
          leaf bundle-status {
            description
              "BUNDLE/UNBUNDLE messages";
            type empty;
          }
          leaf link-status {
            description
              "UPDOWN and CHANGE messages";
            type empty;
          }
          leaf trunk-status {
            description
              "TRUNK status messages";
            type empty;
          }
          leaf nfas-status {
            description
              "NFAS D-channel status messages";
            type empty;
          }
          leaf power-inline-status {
               description
                  "Inline power messages";
               type empty;
          }
          leaf status {
            description
              "Spanning-tree state change messages";
            type empty;
          }
          container spanning-tree {
            description
              "Spanning-tree Interface events";
            presence "true";
            leaf status {
              description
                "Spanning-tree state change messages";
              type empty;
            }
          }
          container subif-link-status {
            description
              "Sub-interface UPDOWN and CHANGE messages";
            presence "true";
            leaf ignore-bulk {
              description
                "Do not log messages when the main interface is transitioning";
              type empty;
            }
          }
        }
      }
  
      // interface * / mdix
      container mdix {
        description
          "Set Media Dependent Interface with Crossover";
        leaf auto {
          type boolean;
        }
      }
  
      // interface * / mop
      container mop {
          leaf enabled {
           type boolean;
         }
         leaf sysid {
           description
             "Send out MOP periodic system ID messages";
           type boolean;
         }
       }
  
      // interface * / max-reserved-bandwidth
      leaf max-reserved-bandwidth {
        description
          "Maximum Reservable Bandwidth on an Interface";
        type uint8 {
          range "1..100";
        }
      }
  
      // @mount Cisco-IOS-XE-mls
  
      // interface * / mtu
      leaf mtu {
        description
          "Set the interface Maximum Transmission Unit (MTU)";
        type uint16 {
          range "64..18000";
        }
      }
  
      // interface * / ospfv3
      // @mount Cisco-IOS-XE-ospfv3
  
  
      // interface * / power
      //@mount Cisco-IOS-XE-power
  
      // interface * / qos
      container interface_qos {
        container trust {
          leaf device {
            type enumeration {
              enum "cisco-phone";
            }
          }
        }
      }
      // interface * / service-policy
      // @mount Cisco-IOS-XE-policy
  
      // interface * / service-insertion
      leaf service-insertion {
        description
          "Service-insertion AppNav Controller";
        type enumeration {
          enum "waas";
        }
      }
  
      // interface * / standby
      container standby {
        description
          "HSRP interface configuration commands";
        leaf version {
          description
            "HSRP version";
          type enumeration {
            enum "1";
            enum "2";
          }
        }
  
        // interface * / standby bfd
        leaf bfd {
          description
            "Enable HSRP BFD";
          type empty;
        }
  
        // interface * / standby delay
        container delay {
          description
            "HSRP initialisation delay";
          leaf minimum {
            description
              "Minimum delay";
            type uint16 {
              range "0..10000";
            }
          }
          leaf reload {
            description
              "Delay after reload";
            type uint16 {
              range "0..10000";
            }
          }
        }
  
        // interface * / standby mac-refresh
        leaf mac-refresh {
          description
            "Refresh MAC cache on switch by periodically sending packet from virtual mac address";
          type uint8 {
            range "0..255";
          }
        }
  
        // interface * / standby use-bia
        container use-bia {
          description
            "HSRP uses interface's burned in address";
          presence "true";
          container scope {
            description
              "Specify the scope of use-bia";
            leaf interface {
              description
                "Use-bia applies to all groups on this interface or sub-interface";
              type empty;
            }
          }
        }
  
        // interface * / standby *
        list standby-list {
          key "group-number";
          leaf group-number {
            type uint16;
          }
          container authentication {
            description
              "Authentication";
            choice auth {
              leaf word {
                type string;
              }
              container md5 {
                description
                  "Use MD5 authentication";
                leaf key-chain {
                  description
                    "Set key chain";
                  type string;
                }
                container key-string {
                  description
                    "Set key string";
                  leaf encrypt {
                    type enumeration {
                      enum "0";
                      enum "7";
                    }
                  }
                  leaf string {
                    type string;
                  }
                  leaf timeout {
                    description
                      "Set timeout";
                    type uint16 {
                      range "0..32767";
                    }
                  }
                }
              }
              leaf text {
                description
                  "Plain text authentication";
                type string;
              }
            }
          }
          leaf follow {
            description
              "Name of HSRP group to follow";
            type string;
          }
          container ip {
            description
              "Enable HSRP and set the virtual IP address";
            presence "true";
            leaf address {
              type inet:ipv4-address;
            }
            leaf secondary {
              description
                "Make this IP address a secondary virtual IP address";
              type empty;
            }
          }
          leaf ipv6 {
            description
              "Enable HSRP IPv6";
            type union {
              type inet:ipv6-address;
              type ios-types:ipv6-prefix;
              type enumeration {
                enum "autoconfig";
              }
            }
          }
          leaf mac-address {
            description
              "Virtual MAC address";
            type string;
          }
          leaf name {
            description
              "Redundancy name string";
            type string;
          }
          container preempt {
            description
              "Overthrow lower priority Active routers";
            presence "true";
            container delay {
              description
                "Wait before preempting";
              leaf minimum {
                description
                  "Delay at least this long";
                type uint16 {
                  range "0..3600";
                }
              }
              leaf reload {
                description
                  "Delay after reload";
                type uint16 {
                  range "0..3600";
                }
              }
              leaf sync {
                description
                  "Wait for IP redundancy client";
                type uint16 {
                  range "0..3600";
                }
              }
            }
          }
          leaf priority {
            description
              "Priority level";
            type uint8;
          }
          container redirect {
            description
              "Configure sending of ICMP Redirect messages with an HSRP virtual IP address as the gateway IP address";
            container advertisement {
              description
                "Redirect advertisement messages";
              container authentication {
                description
                  "Authentication";
                container md5 {
                  description
                    "Use MD5 authentication";
                  leaf key-chain {
                    description
                      "Set key chain";
                    type string;
                  }
                  container key-string {
                    description
                      "Set key string";
                    leaf encrypt {
                      type enumeration {
                        enum "0";
                        enum "7";
                      }
                    }
                    leaf string {
                      type string;
                    }
                    leaf timeout {
                      description
                        "Set timeout";
                      type uint16 {
                        range "0..32767";
                      }
                    }
                  }
                }
              }
            }
            container timers {
              description
                "Adjust redirect timers";
              leaf advertisement {
                type uint16 {
                  range "10..180";
                }
              }
              leaf holddown {
                type uint16 {
                  range "30..3600";
                }
              }
            }
            leaf unknown {
              description
                "Redirect to non-HSRP routers";
              type empty;
            }
          }
          container timers {
            description
              "Hello and hold timers";
            container hello-interval {
              choice hello-interval-choice {
                leaf seconds {
                  type uint8 {
                    range "1..254";
                  }
                }
                leaf msec {
                  description
                    "Specify hello interval in milliseconds";
                  type uint16 {
                    range "15..999";
                  }
                }
              }
            }
            container hold-time {
              choice hold-time-choice {
                leaf seconds {
                  type uint8 {
                    range "1..255";
                  }
                }
                leaf msec {
                  description
                    "Specify hold time in milliseconds";
                  type uint16 {
                    range "50..3000";
                  }
                }
              }
            }
          }
          list track {
            description
              "Priority tracking";
            key "number";
            leaf number {
              type uint16 {
                range "1..1000";
              }
            }
            leaf decrement {
              description
                "Priority decrement";
              type uint8;
            }
            leaf shutdown {
              description
                "Shutdown group";
              type empty;
            }
          }
        }
      }
  
      // interface * / access-session
      container access-session {
        description "Access Session specific Interface Configuration Commands";
        leaf closed {
          description
            "Enable closed access on port (disabled by default, i.e. open access)";
          type empty;
        }
        container port-control {
          description "Set the port-control value";
          leaf auto {
            description "PortState set to automatic";
            type empty;
          }
        }
        leaf host-mode {
          description
            "Set the Host mode for authentication on this interface";
          type enumeration {
            enum "multi-auth";
            enum "multi-domain";
            enum "multi-host";
            enum "single-host";
          }
        }
      }
      // interface * / storm-control
      container storm-control {
        description
          "storm configuration";
        container action {
          description
            "Action to take for storm..control;";
          leaf level {
            description
              "Set storm suppression level on this interface";
            type decimal64 {
              fraction-digits 2;
              range "0..100";
            }
          }
          leaf shutdown {
            description
              "Shutdown this interface if a storm occurs";
              type empty;
          }
          leaf trap {
              description
                "Send SNMP trap if a storm occurs";
              type empty;
          }
        }
        container broadcast {
          description
            "Broadcast address storm control";
          container include {  // not in 3850
            leaf multicast {
              type empty;
            }
          }
          uses storm-control-threshold-grouping; 
        }
        container multicast {
          description
            "Multicast address storm control";
          uses storm-control-threshold-grouping; 
        }
        container unicast {
          description
            "Unicast address storm control";
          uses storm-control-threshold-grouping; 
        }
      }
      // interface * / trust
      container trust {
        description
          "Set trust value for the interface";
        leaf device {
          description
            "trusted device class";
          type enumeration {
            enum cisco-phone;
            enum cts;
            enum ip-camera;
            enum media-player;
          }
        }
      }
  
      // interface * / wrr-queue (unused)
      // @mount Cisco-IOS-XE-qos
  
      // interface * / priority-queue
      container priority-queue {
        description
          "Configure priority scheduling";
        container cos-map {
          description
            "Configure cos-map for a queue";
          leaf id {
            type uint8;
          }
          leaf-list cos-values {
            max-elements "8";
            type uint8 {
              range "0..7";
            }
          }
        }
        leaf out {
          description
            "egress priority queue";
          type empty;
        }
        //  queue-limit  Configure priority queue limit
      }
  
      // interface * / rep
      // @mount Cisco-IOS-XE-switch
  
      // interface * / rcv-queue
      container rcv-queue {
        description
          "Configure receive queue(s)";
        list cos-map {
          description
            "Configure cos-map for a queue threshold";
          key "queue-id threshold-id";
          leaf queue-id {
            type uint8 {
              range "1..3";
            }
          }
          leaf threshold-id {
            type uint8 {
              range "1..8";
            }
          }
          leaf-list cos-values {
            max-elements "8";
            type uint8 {
              range "0..7";
            }
          }
        }
      }
  
      // interface * / udld
  
      // interface * / peer
      container peer {
        description
          "Peer parameters for point to point interfaces";
        container default {
          description
            "Specify default parameters";
          container ip {
            description
              "Specify default IP parameters";
            container address {
              description
                "Specify default IP address";
              choice address-choice {
                leaf dhcp {
                  description
                    "Use DHCP proxy client mechanism to allocate a peer IP address";
                  type empty;
                }
                container dhcp-pool {
                  description
                    "Use local DHCP pools to allocate a peer IP address";
                  presence "true";
                  leaf pools {
                    type string;
                  }
                }
                container pool {
                  description
                    "Use IP pool mechanism to allocate a peer IP address";
                  presence "true";
                  leaf pools {
                    type string;
                  }
                }
              }
            }
          }
        }
      }
      // interface * / pm-path
      container pm-path {
        description
            "Global pm-path configuration";
        leaf name {
          description
          "WORD Path name";
          type string;
        }
        leaf interface-id {
          description
          "<1-255> Specify the interface-id value";
          type uint8 {
          range "1..255";
          }
        }
      }
  
      // interface * / performance monitor
      //@mount Cisco-IOS-XE-ezpm
  
      // interface * / macsec
      //@mount Cisco-IOX-XE-switch
  
      //interface * / mka
      //@mount Cisco-IOS-XE-mka
    }
  
    /////////////////////////////////////////////////////////
    // native / interface
    /////////////////////////////////////////////////////////
    grouping config-interface-grouping {
      container interface { 
        description
          "Configure Interfaces";
  
        // interface AppNav-Compress
        list AppNav-Compress {
          description
            "Service-Context Virtual Interface Compress";
          key "name";
          leaf name {
            type uint16 {
              range "1..1000";
            }
          }
          uses interface-common-grouping;
        }
  
        // interface AppNav-UnCompress
        list AppNav-UnCompress {
          description
            "Service-Context Virtual Interface UnCompress";
          key "name";
          leaf name {
            type uint16 {
              range "1..1000";
            }
          }
          uses interface-common-grouping;
        }
  
        // interface ATM #
        list ATM {
          description
            "ATM interface";
          key "name";
          leaf name {
            type string {
              pattern "([0-9]/){2}([0-9]|(ima[0-9]))(:[0-9])?";
            }
          }
        }
  
        // subinterface ATM #.#
        container ATM-subinterface {
          list ATM {
            key "name";
            leaf name {
              type string {
                pattern "([0-9]/){2}[0-9]\\.([0-9]/){3}[0-9]";
              }
            }
          }
        }
  
        // interface ATM-ACR #
        list ATM-ACR {
          description
            "ATM-ACR interface";
          key "name";
          leaf name {
            type string {
              pattern "[0-9]";
            }
          }
        }
  
        // subinterface ATM-ACR #.#
        container ATM-ACRsubinterface {
          list ATM-ACR {
            key "name";
            leaf name {
              type string {
                pattern "[0-9]\\.([0-9]/){3}[0-9]";
              }
            }
          }
        }
  
        // interface BDI
        list BDI {
          description
            "Bridge-Domain interface";
          key "name";
          leaf name {
            type string;
          }
          uses interface-common-grouping;
        }
  
        // interface CEM #
        list CEM {
          description
            "Circuit Emulation interface";
          key "name";
          leaf name {
            type string {
              pattern "([0-9]/){2}[0-9]";
            }
          }
        }
  
        // interface CEM-ACR #
        list CEM-ACR {
          description
            "Circuit Emulation interface";
          key "name";
          leaf name {
            type uint8 {
              range "0..255";
            }
          }
        }
  
        // interface Embedded-Service-Engine
        list Embedded-Service-Engine {
          description
            "cisco embedded service engine module";
          key "name";
          leaf name {
            type string;
          }
          uses interface-common-grouping;
        }
  
        // interface FastEthernet
        list FastEthernet {
          description
            "FastEthernet IEEE 802.3";
          key "name";
          leaf name {
            type string {
              pattern "([0-9]/)([0-9]/)([1-3][0-9]|4[0-8]|[0-9])(\\.[0-9]+)?";
            }
           }
           uses interface-common-grouping;
         }
   
          // interface ucse 
         list ucse {
           description
             "Cisco ucse server";
           key "name";
           leaf name {
             type string;
           }
           uses interface-negotiation-grouping;
           uses interface-switchport-grouping;
           uses interface-common-grouping;
         }
   
         // interface Ethernet-Internal 
         list Ethernet-Internal {
           description
             "Ethernet-Internal interface";
           key "name";
           leaf name {
             type string;
           }
           uses interface-negotiation-grouping;
           uses interface-switchport-grouping;
           uses interface-common-grouping;
         }
   
         // interface Service-Engine 
         list Service-Engine {
           description
             "Cisco service engine module";
           key "name";
           leaf name {
             type string;
           }
            uses interface-common-grouping;
          }
  
        // interface GigabitEthernet
        list GigabitEthernet {
          description
            "GigabitEthernet IEEE 802.3z";
          key "name";
          leaf name {
            type string;
          }
          leaf media-type {
            description
              "Media type";
            type enumeration {
              enum "auto-select";
              enum "rj45";
              enum "sfp";
            }
          }
          leaf port-type {
            type enumeration {
              enum "nni";
            }
          }
          uses interface-common-grouping;
        }
  
        // interface FiveGigabitEthernet
        list FiveGigabitEthernet {
          description
            "Five Gigabit Ethernet";
          key "name";
          leaf name {
            type string;
          }
          leaf media-type {
            description
              "Media type";
            type enumeration {
              enum "auto-select";
              enum "rj45";
              enum "sfp";
            }
          }
          leaf port-type {
            type enumeration {
              enum "nni";
            }
          }
          uses interface-common-grouping;
        }
  
        // interface TenGigabitEthernet
        list TenGigabitEthernet {
          description
            "Ten Gigabit Ethernet";
          key "name";
          leaf name {
            type string;
          }
          leaf media-type {
            description
              "Media type";
            type enumeration {
              enum "auto-select";
              enum "rj45";
              enum "sfp";
            }
          }
          leaf port-type {
            type enumeration {
              enum "nni";
            }
          }
          uses interface-common-grouping;
        }
        // interface FiveGigabitEthernet
        list TwentyFiveGigabitEthernet {
          description
            "Twenty Five Gigabit Ethernet";
          key "name";
          leaf name {
            type string;
          }
          leaf media-type {
            description
              "Media type";
            type enumeration {
              enum "auto-select";
              enum "rj45";
              enum "sfp";
            }
          }
          leaf port-type {
            type enumeration {
              enum "nni";
            }
          }
          uses interface-common-grouping;
        }
  
        // interface FortyGigabitEthernet
        list FortyGigabitEthernet {
          description
            "Forty Gigabit Ethernet";
          key "name";
          leaf name {
            type string;
          }
          leaf media-type {
            description
              "Media type";
            type enumeration {
              enum "auto-select";
              enum "rj45";
              enum "sfp";
            }
          }
          leaf port-type {
            type enumeration {
              enum "nni";
            }
          }
          uses interface-common-grouping;
        }
  
        // interface HundredGigE
        list HundredGigE {
          description
            "Hundred Gigabit Ethernet";
          key "name";
          leaf name {
            type string;
          }
          uses interface-common-grouping;
        }
  
        // interface Loopback
        list Loopback {
          description
            "Loopback interface";
          key "name";
          leaf name {
            type uint32;
          }
          uses interface-common-grouping;
        }
  
        // interface LISP
        list LISP {
          description
            "Locator/ID Separation Protocol Virtual Interface";
          key "name";
          leaf name {
  //PVH          type string;
            type uint16 {
              range "0..65520";
            }
          }
          uses interface-common-grouping;
        }
        //interface LISP subinterface
        container LISP-subinterface {
          description
            "Locator/ID Separation Protocol Virtual Interface";
          list LISP  {
            key "name";
            leaf name {
              type string {
                pattern "[0-9]*(. ?[1-9][0-9]*)*";
              }
            }
            uses interface-common-grouping;
          }
        }
  
        list nve {
          description
            "Network virtualization endpoint interface";
          key "name";
          leaf name {
            type uint16 {
              range "1..4096";
            }
          }
          container group-based {
            description
              "group based policy mode";
            leaf policy {
              type empty;
            }
          }
          container source-interface {
            description
              "Specify source interface for NVE";
            uses ios-ifc:interface-grouping;
          }
          container member-in-one-line {
             container member {
               list vni {
                 description
                   "Configure VNI information";
                 key "vni-range";
                 leaf vni-range {
                   type string;
                 }
                 leaf vrf { 
                   description
                     "Specify a particular VRF";
                   type string; 
                 }
               }
             }
           }
          container member {
            list vni {
              description
                "Configure VNI information";
              key "vni-range";
              leaf vni-range {
                type string;
              }
              container default {
                 uses nve-member-vni-grouping; 
               }
               uses nve-member-vni-grouping; 
               container no {
                 uses nve-member-vni-grouping; 
                }
              }
            }
           uses interface-common-grouping;
          }
  
        // interface overlay
        list overlay {
          description
            "Overlay interface";
          key "name";
          leaf name {
            type uint16 {
              range "0..512";
            }
          }
        }
  
        // interface Port-channel
        list Port-channel {
          description
            "Ethernet Channel of interfaces";
          key "name";
          leaf name {
            type uint32 {
              range "1..512";
           }
          }
          leaf pc-speed {
            description
              "Configure speed operation.";
            type enumeration {
              enum "10";
              enum "100";
              enum "1000";
              enum "nonegotiate";
              enum "auto";
            }
          }
          container port-channel {
            description "Port Channel interface subcommands";
            leaf min-links {
              description "Minimum number of bundled ports needed to bring up "
                         +"     this port channel";
              type uint8 {
                range "2..8";
              }
            }
            leaf standalone-disable {
              description "Ports will go to suspended mode if peer does not "
                         +"respond. Use with [no] prefix for independent mode.";
              type empty;
            }
          }
          uses interface-common-grouping;
        }
  
        // subinterface Port-channel #.#
        container Port-channel-subinterface {
          list Port-channel {
            key "name";
            leaf name {
              type string;
            }
            uses interface-common-grouping;
          }
        }
  
        //interface pseudowire
        list pseudowire {
          description
            "Pseudowire Interface";
          key "name";
          leaf name {
            type uint32 {
              range "1..231072";
            }
          }
        }
  
        //interface SM
        list SM {
          description
            "SM Interface";
          key "name";
          leaf name {
            type string {
              pattern "([0-9])+(/([0-9])+)?";
            }
          }
          uses interface-common-grouping;
        }
  
        //interface Cellular
        list Cellular {
          description
            "Cellular Interface";
          key "name";
          leaf name {
            type string {
              pattern "([0-9])+(/([0-9])+)?";
            }
          }
          uses interface-common-grouping;
          //@mount Cisco-IOS-XE-cellular
        }
  
        // interface Vlan
        list Vlan {
          description
            "Catalyst Vlans";
          key "name";
          leaf name {
            type uint16 {
              range "1..4094";
            }
          }
          uses interface-common-grouping;
          //@mount Cisco-IOS-XE-vlan
        }
  
        // interface Group-Async
        list Group-Async {
          description
            "Async Group interface";
          key "name";
          leaf name {
            type uint16 {
              range "0..64";
            }
          }
          leaf physical-layer {
            description
              "Configure sync or async physical layer on serial interface";
            type enumeration {
              enum "async";
              enum "sync";
            }
          }
          uses interface-common-grouping;
        }
  
        // interface Multilink
        list Multilink {
          description
            "Multilink-group interface";
          key "name";
          leaf name {
            type uint16 {
              range "1..65535";
            }
          }
          uses interface-common-grouping;
        }
  
        // interface Serial
        list Serial {
          description
            "Serial interface";
          key "name";
          leaf name {
            type string {
              pattern "([0-9])+/([0-9])+/([0-9])+\\.([0-9])+/([0-9])+/([0-9])+/([0-9])+:([0-9])";
            }
          }
          uses interface-common-grouping;
        }
  
        // interface Tunnel #
        list Tunnel {
          description
            "Tunnel interface";
          key "name";
          leaf name {
            type uint32;
          }
          uses interface-common-grouping;
          // interface Tunnel* / qos
          container qos {
            description
              "Quality of Service related commands";
            leaf pre-classify {
              description
                "Enable QOS classification before packets are tunnel encapsulated";
              type empty;
            }
          }
        }
  
        // interface Virtual-Template
        list Virtual-Template {
          description
            "Virtual Template interface";
          key "name";
          leaf name {
            type uint16 {
              range "1..4095";
            }
          }
          leaf type {
            description
              "type of the virtual-template";
            type enumeration {
              enum "ethernet";
              enum "serial";
              enum "tunnel";
              enum "vpn";
            }
          }
          uses interface-common-grouping;
        }
  
        // interface VirtualPortGroup
        list VirtualPortGroup {
          description
            "Virtual Port Group";
          key "name";
          leaf name {
            type uint16 {
              range "0..31";
            }
          }
          uses interface-common-grouping;
        }
  
        // interface vasileft
        list vasileft {
          description
            "vasileft";
          key "name";
          leaf name {
            type uint16 {
              range "1..2000";
            }
          }
          uses interface-common-grouping;
        }
  
        // interface vasiright
        list vasiright {
          description
            "vasiright";
          key "name";
          leaf name {
            type uint16 {
              range "1..2000";
            }
          }
          uses interface-common-grouping;
        }
      }
    }
  }
